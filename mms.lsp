(defun dtr(x) (* (/ pi 180.0) x))
(defun rtd(x) (* (/ 180 pi) x))


(defun c:mms_vba()
  
  (settings_mms)
  (mms_nil)
  (command "vbarun" "C:/mymenu/Project.dvb!Module1.ShowUserForm")
)

(defun c:mms()
    (setq p1 (getpoint "\n Pick the point to generate the Drawing::"))
    (if (= p1 nil) (setq p1 (getpoint "\n Pick the point to generate the Drawing::")))
  ;; solar module
    (setq s1 (polar p1 (dtr mms_angle) module_bolt1)) ;bolt1 bottom
    (setq s2 (polar s1 (dtr mms_angle) module_boltgap)) ;bolt2 bottom
    (setq s3 (polar s2 (dtr mms_angle) module_botl2))
    (setq s4 (polar s3 (dtr (+ 90 mms_angle)) 35))
    (setq s5 (polar s4 (dtr mms_angle) (- module_botl2))) ;bolt2
    (setq s6 (polar s5 (dtr mms_angle) (- module_boltgap))) ;bolt1
    (setq s7 (polar s6 (dtr mms_angle) (- module_bolt1)))
    ;(command "_pline" p1 s1 s2 s3 s4 s5 s6 s7 "c")
    (setq s8 (polar s3 (dtr mms_angle) 20))
    (setq s9 (polar s8 (dtr mms_angle) module_bolt1)) ;bolt1 bottom
    (setq s10 (polar s9 (dtr mms_angle) module_boltgap)) ;bolt2 bottom
    (setq s11 (polar s10 (dtr mms_angle) module_botl2))
    (setq s12 (polar s11 (dtr (+ 90 mms_angle)) 35))
    (setq s13 (polar s12 (dtr mms_angle) (- module_botl2))) ;bolt2
    (setq s14 (polar s13 (dtr mms_angle) (- module_boltgap))) ;bolt1
    (setq s15 (polar s14 (dtr mms_angle) (- module_bolt1))) 
    ;(command "_pline" s8 s9 s10 s11 s12 s13 s14 s15 "c")

  ;; Purlin-1
    (setq pur1 (polar (polar s1 (dtr mms_angle) (/ Pur_size2 2)) (dtr (+ 270 mms_angle)) Pur_size3))
    (setq pur2 (polar pur1 (dtr (+ 90 mms_angle)) Pur_size3))
    (setq pur3 (polar pur2 (dtr (+ 180 mms_angle)) Pur_size2))
    (setq pur4 (polar pur3 (dtr (+ 270 mms_angle)) Pur_size1))
    (setq pur5 (polar pur4 (dtr mms_angle) Pur_size2))
    (setq pur6 (polar pur5 (dtr (+ 90 mms_angle)) Pur_size3))
    (setq pur7 (polar pur6 (dtr (+ 180 mms_angle)) Pur_tick))
    (setq pur8 (polar pur7 (dtr (+ 270 mms_angle)) (- Pur_size3 Pur_tick)))
    (setq pur9 (polar pur8 (dtr (+ 180 mms_angle)) (- Pur_size2 Pur_tick Pur_tick)))
    (setq pur10 (polar pur9 (dtr (+ 90 mms_angle)) (- Pur_size1 Pur_tick Pur_tick)))
    (setq pur11 (polar pur10 (dtr mms_angle) (- Pur_size2 Pur_tick Pur_tick)))
    (setq pur12 (polar pur11 (dtr (+ 270 mms_angle)) (- Pur_size3 Pur_tick)))
    ;(command "_pline" pur1 pur2 pur3 pur4 pur5 pur6 pur7 pur8 pur9 pur10 pur11 pur12 "c")
  ;Purlin-1 cleat
    (setq pur13 (polar pur4 (dtr (+ 180 mms_angle)) Pur_size2))
    (setq pur14 (polar pur13 (dtr (+ 90 mms_angle)) 2))
    (setq pur15 (polar pur14 (dtr mms_angle) (- Pur_size2 2)))
    (setq pur16 (polar pur15 (dtr (+ 90 mms_angle)) (- Pur_size1 7)))
    (setq pur17 (polar pur16 (dtr mms_angle) 2))
    ;(command "_pline" pur4 pur13 pur14 pur15 pur16 pur17 "c")
   ; (cen)(purcleatbolts pur4)
  ;; Purlin-2
    (setq pur18 (polar (polar s2 (dtr mms_angle) (/ Pur_size2 2)) (dtr (+ 270 mms_angle)) Pur_size3))
    (setq pur19 (polar pur18 (dtr (+ 90 mms_angle)) Pur_size3))
    (setq pur20 (polar pur19 (dtr (+ 180 mms_angle)) Pur_size2))
    (setq pur21 (polar pur20 (dtr (+ 270 mms_angle)) Pur_size1))
    (setq pur22 (polar pur21 (dtr mms_angle) Pur_size2))
    (setq pur23 (polar pur22 (dtr (+ 90 mms_angle)) Pur_size3))
    (setq pur24 (polar pur23 (dtr (+ 180 mms_angle)) Pur_tick))
    (setq pur25 (polar pur24 (dtr (+ 270 mms_angle)) (- Pur_size3 Pur_tick)))
    (setq pur26 (polar pur25 (dtr (+ 180 mms_angle)) (- Pur_size2 Pur_tick Pur_tick)))
    (setq pur27 (polar pur26 (dtr (+ 90 mms_angle)) (- Pur_size1 Pur_tick Pur_tick)))
    (setq pur28 (polar pur27 (dtr mms_angle) (- Pur_size2 Pur_tick Pur_tick)))
    (setq pur29 (polar pur28 (dtr (+ 270 mms_angle)) (- Pur_size3 Pur_tick)))
    ;(command "_pline" pur18 pur19 pur20 pur21 pur22 pur22 pur23 pur24 pur25 pur26 pur27 pur28 pur29 "c")
  ;Purlin-2 cleat
    (setq pur30 (polar pur21 (dtr (+ 180 mms_angle)) Pur_size2))
    (setq pur31 (polar pur30 (dtr (+ 90 mms_angle)) 2))
    (setq pur32 (polar pur31 (dtr mms_angle) (- Pur_size2 2)))
    (setq pur33 (polar pur32 (dtr (+ 90 mms_angle)) (- Pur_size1 7)))
    (setq pur34 (polar pur33 (dtr mms_angle) 2))
    ;(command "_pline" pur21 pur30 pur31 pur32 pur33 pur34 "c")
  ;  (cen)(purcleatbolts pur21)
  ;;;
  ;; Purlin-3
    (setq pur35 (polar (polar s9 (dtr mms_angle) (/ Pur_size2 2)) (dtr (+ 270 mms_angle)) Pur_size3))
    (setq pur36 (polar pur35 (dtr (+ 90 mms_angle)) Pur_size3))
    (setq pur37 (polar pur36 (dtr (+ 180 mms_angle)) Pur_size2))
    (setq pur38 (polar pur37 (dtr (+ 270 mms_angle)) Pur_size1))
    (setq pur39 (polar pur38 (dtr mms_angle) Pur_size2))
    (setq pur40 (polar pur39 (dtr (+ 90 mms_angle)) Pur_size3))
    (setq pur41 (polar pur40 (dtr (+ 180 mms_angle)) Pur_tick))
    (setq pur42 (polar pur41 (dtr (+ 270 mms_angle)) (- Pur_size3 Pur_tick)))
    (setq pur43 (polar pur42 (dtr (+ 180 mms_angle)) (- Pur_size2 Pur_tick Pur_tick)))
    (setq pur44 (polar pur43 (dtr (+ 90 mms_angle)) (- Pur_size1 Pur_tick Pur_tick)))
    (setq pur45 (polar pur44 (dtr mms_angle) (- Pur_size2 Pur_tick Pur_tick)))
    (setq pur46 (polar pur45 (dtr (+ 270 mms_angle)) (- Pur_size3 Pur_tick)))
    ;(command "_pline" pur35 pur36 pur37 pur38 pur39 pur40 pur41 pur42 pur43 pur44 pur45 pur46 "c")
  ;Purlin-3 cleat
    (setq pur47 (polar pur38 (dtr (+ 180 mms_angle)) Pur_size2))
    (setq pur48 (polar pur47 (dtr (+ 90 mms_angle)) 2))
    (setq pur49 (polar pur48 (dtr mms_angle) (- Pur_size2 2)))
    (setq pur50 (polar pur49 (dtr (+ 90 mms_angle)) (- Pur_size1 7)))
    (setq pur51 (polar pur50 (dtr mms_angle) 2))
    ;(command "_pline" pur38 pur47 pur48 pur49 pur50 pur51 "c")
  ;  (cen)(purcleatbolts pur38)
  ;; Purlin-4
    (setq pur52 (polar (polar s10 (dtr mms_angle) (/ Pur_size2 2)) (dtr (+ 270 mms_angle)) Pur_size3))
    (setq pur53 (polar pur52 (dtr (+ 90 mms_angle)) Pur_size3))
    (setq pur54 (polar pur53 (dtr (+ 180 mms_angle)) Pur_size2))
    (setq pur55 (polar pur54 (dtr (+ 270 mms_angle)) Pur_size1))
    (setq pur56 (polar pur55 (dtr mms_angle) Pur_size2))
    (setq pur57 (polar pur56 (dtr (+ 90 mms_angle)) Pur_size3))
    (setq pur58 (polar pur57 (dtr (+ 180 mms_angle)) Pur_tick))
    (setq pur59 (polar pur58 (dtr (+ 270 mms_angle)) (- Pur_size3 Pur_tick)))
    (setq pur60 (polar pur59 (dtr (+ 180 mms_angle)) (- Pur_size2 Pur_tick Pur_tick)))
    (setq pur61 (polar pur60 (dtr (+ 90 mms_angle)) (- Pur_size1 Pur_tick Pur_tick)))
    (setq pur62 (polar pur61 (dtr mms_angle) (- Pur_size2 Pur_tick Pur_tick)))
    (setq pur63 (polar pur62 (dtr (+ 270 mms_angle)) (- Pur_size3 Pur_tick)))
    ;(command "_pline" pur52 pur53 pur54 pur55 pur56 pur57 pur58 pur59 pur60 pur61 pur62 pur63 "c")
  ;Purlin-4 cleat
    (setq pur64 (polar pur55 (dtr (+ 180 mms_angle)) Pur_size2))
    (setq pur65 (polar pur64 (dtr (+ 90 mms_angle)) 2))
    (setq pur66 (polar pur65 (dtr mms_angle) (- Pur_size2 2)))
    (setq pur67 (polar pur66 (dtr (+ 90 mms_angle)) (- Pur_size1 7)))
    (setq pur68 (polar pur67 (dtr mms_angle) 2))
    ;(command "_pline" pur55 pur64 pur65 pur66 pur67 pur68 "c")
  ;  (cen)(purcleatbolts pur55)

  ;; Rafter
    (setq raf1 (polar pur13 (dtr (+ 180 mms_angle)) rf1_size2))
    (setq raf2 (polar pur56 (dtr mms_angle) rf1_size2))
    (setq raf3 (polar raf2 (dtr (+ 270 mms_angle)) rf1_size1))
    (setq raf4 (polar raf3 (dtr (+ 180 mms_angle)) (distance raf1 raf2)))
  ;;hiden lines
    (setq raf5 (polar raf1 (dtr (+ 270 mms_angle)) rf1_size3))
    (setq raf6 (polar raf2 (dtr (+ 270 mms_angle)) rf1_size3))
    (setq raf7 (polar raf4 (dtr (+ 90 mms_angle)) rf1_size3))
    (setq raf8 (polar raf3 (dtr (+ 90 mms_angle)) rf1_size3))

    (setq raf9 (polar raf1 (dtr (+ 270 mms_angle)) rf1_tick))
    (setq raf10 (polar raf2 (dtr (+ 270 mms_angle)) rf1_tick))
    (setq raf11 (polar raf4 (dtr (+ 90 mms_angle)) rf1_tick))
    (setq raf12 (polar raf3 (dtr (+ 90 mms_angle)) rf1_tick))

    (setq raf13 (polar raf1 (dtr (+ 270 mms_angle)) (/ rf1_size1 2)))
    (setq raf14 (polar raf2 (dtr (+ 270 mms_angle)) (/ rf1_size1 2)))

    (setq Rafter_length (distance raf1 raf2))

   ; (mem)(command "_pline" raf1 raf2 raf3 raf4 "c")
   ; (das)(command "_pline" raf5 raf6 "")(command "_pline" raf7 raf8 "")
   ;     (command "_pline" raf9 raf10 "")(command "_pline" raf11 raf12 "")
   ; (cen)(command "_pline" raf13 raf14 "")

  ;;NLG level
    (setq ngl1 (polar p1 (dtr 270.0) mms_base_hight))
    (setq ngl2 (polar ngl1 (dtr 0.0) (+ 2000 2000 pile_dia)))

    (setq ngl3 (polar ngl1 (dtr 0.0) 800))
    (setq ngl4 (polar ngl2 (dtr 180.0) 800))
    ;(command "_pline" ngl3 ngl4 "")
    ;(command "_text" "J" "L" (polar ngl3 (dtr 90.0) 5) "0" "NGL")
    ;(command "_text" "J" "L" (polar (polar ngl4 (dtr 180.0) 90) (dtr 90.0) 5) "0" "NGL")
    (repeat 5
      ;(command "_pline" (polar ngl3 (dtr 225) 100) ngl3 (polar ngl3 (dtr 315) 100) "")
      (setq ngl3 (polar ngl3 (dtr 0.0) 25))
    )
    (repeat 5
      ;(command "_pline" (polar ngl4 (dtr 225) 100) ngl4 (polar ngl4 (dtr 315) 100) "")
      (setq ngl4 (polar ngl4 (dtr 180.0) 25))
    )
  ;; center line
    (setq cen1 (polar raf13 (dtr mms_angle) (* (- 100 (- 50 (* mms_angle 0.65))) (/ Rafter_length 100)) ))
    (setq cen2 (polar cen1 (dtr 270.0) 2500))
    (setq pile_center (inters ngl1 ngl2 cen1 cen2))
    (setq cen3 (polar pile_center (dtr 270.0) (+ pile_len 20)))
    (setq cen4 (polar cen1 (dtr 90.0) 100))
  ;  (cen)(command "_pline" cen4 cen3 "")
  ;; pile center point
    (setq pl1 (polar pile_center (dtr 180.0) (/ pile_dia 2)))
    (setq pl2 (polar pl1 (dtr 270.0) pile_len))
    (setq pl3 (polar pl2 (dtr 0.0) pile_dia))
    (setq pl4 (polar pl3 (dtr 90.0) pile_len))
    (setq pl5 (polar pl4 (dtr 90.0) pile_cap))
    (setq pl6 (polar pl5 (dtr 180) pile_dia))
  ;  (mem)(command "_pline" pl1 pl2 pl3 pl4 pl5 pl6 "c")
  ;  (color8)(command "hatch" "AR-CONC" "0.5" "0" "l" "")

  ;;Leg3
    (setq leg3_length (* pile_len 0.75))
    (setq leg1leg2_union (+ (- pile_len leg3_length 100) (- pile_len leg3_length 100)))

    (setq lg1 (polar (polar (inters pl2 pl3 cen1 cen2) (dtr 90.0) 100) (dtr 0.0) (/ leg3_size1 2))
          lg2 (polar lg1 (dtr 90.0) leg3_length)
          lg3 (polar lg2 (dtr 180.0) leg3_size1)
          lg4 (polar lg3 (dtr 270.0) leg3_length)
    )
  ;  (mem)(command "_pline" lg1 lg2 lg3 lg4 "c")
   ;hidden lines
    (setq lg5 (polar lg1 (dtr 180.0) leg3_tick))
    (setq lg6 (polar lg5 (dtr 90.0) leg3_length))
    (setq lg7 (polar lg4 (dtr 0.0) leg3_tick))
    (setq lg8 (polar lg7 (dtr 90.0) leg3_length))
  ;  (das)(command "_pline" lg5 lg6 "") (command "_pline" lg7 lg8 "")
  ;;Leg1
    (setq lg9 (polar (inters cen4 cen3 raf1 raf2) (dtr 0.0) (/ leg1_size1 2)))
    (setq lg10 (polar lg9 (dtr 180.0) leg1_size1))
    (setq lg11 (polar (polar pile_center (dtr 270.0) (- (+ leg3_length 100) leg1leg2_union)) (dtr 180.0) (/ leg1_size1 2)))
    (setq lg12 (polar lg11 (dtr 0.0) leg1_size1))
 ;   (mem)(command "_pline" lg9 lg10 lg11 lg12 "c")
  ;  (das)(command "_pline" (polar lg9 (dtr 180.0) leg1_tick) (polar lg12 (dtr 180.0) leg1_tick) "")
  ;       (command "_pline" (polar lg10 (dtr 0.0) leg1_tick) (polar lg11 (dtr 0.0) leg1_tick) "")
 ;   (des)(command "_pline" (polar lg9 (dtr 180.0) leg1_size3) (polar lg12 (dtr 180.0) leg1_size3) "")
 ;        (command "_pline" (polar lg10 (dtr 0.0) leg1_size3) (polar lg11 (dtr 0.0) leg1_size3) "")
  ;; Leg to Rafter bolts
    (setq lg_bolt1 (/ (- leg1_size1 leg1_size3 leg1_size3) 2)) ; bolt center to center dist
    (setq lg_bolt2 (/ (- leg1_size1 lg_bolt1) 2)) ; first bolt distance from right side
    (setq lg13 (polar lg9 (dtr 180) lg_bolt2))
    (setq lg14 (polar lg13 (dtr 270) 1000))
    (setq lg15 (polar lg13 (dtr 180) lg_bolt1))
    (setq lg16 (polar lg15 (dtr 270) 1000))

 ;   (boltss (inters raf13 raf14 lg13 lg14) 12 0)
 ;   (boltss (inters raf13 raf14 lg15 lg16) 12 0)

    ;Leg1 to Leg2 connection bolts
      (setq lg17 (polar lg6 (dtr 180.0) (+ leg1_size3 (/ (- leg3_size1 leg1_size1) 2) 15)))
      (setq lg18 (polar lg8 (dtr 0.0) (+ leg1_size3 (/ (- leg3_size1 leg1_size1) 2) 15)))
      (setq lg19 (polar lg17 (dtr 270.0) 25))
      (setq lg20 (polar lg18 (dtr 270.0) 25))
      (setq lg21 (polar lg19 (dtr 270.0) (/ (- leg1leg2_union 50) 2)))
      (setq lg22 (polar lg20 (dtr 270.0) (/ (- leg1leg2_union 50) 2)))
      (setq lg23 (polar lg21 (dtr 270.0) (/ (- leg1leg2_union 50) 2)))
      (setq lg24 (polar lg22 (dtr 270.0) (/ (- leg1leg2_union 50) 2)))

  ;  (boltss lg19 12 0)(boltss lg21 12 0)(boltss lg23 12 0)
  ;  (boltss lg20 12 0)(boltss lg22 12 0)(boltss lg24 12 0)

  ;;Gus Plate
    (setq gusplate_wid1 (+ leg1_size1 210))
    (setq gusplate_wid2 100)
    (setq gu1 (polar (polar pile_center (dtr 90.0) (+ pile_cap mms_gus_gap)) (dtr 0.0) (/ gusplate_wid1 2)))
    (setq gu2 (polar gu1 (dtr 90.0) gusplate_wid2))
    (setq gu3 (polar gu2 (dtr 180.0) gusplate_wid1))
    (setq gu4 (polar gu3 (dtr 270.0) gusplate_wid2))
  ;  (mem) (command "_pline" gu1 gu2 gu3 gu3 gu4 "c")
  ;; GUS Plate Bolts
  ;  (cen) (boltss (polar pile_center (dtr 90) (+ pile_cap mms_gus_gap 25)) 18 90)
  ;        (boltss (polar pile_center (dtr 90) (+ pile_cap mms_gus_gap 75)) 18 0)
  ;;Bracings
    (setq br1 (polar (polar (polar pur4 (dtr mms_angle) (/ Pur_size2 2)) (dtr (+ mms_angle 270)) (/ rf1_size1 2)) (dtr mms_angle) 150)) ;brc1 cen line
    (setq br2 (polar (polar gu4 (dtr 90.0) (/ gusplate_wid2 2)) (dtr 0.0) 60)) ; brc1 cen line
    (setq br3 (polar (polar (polar pur55 (dtr mms_angle) (/ Pur_size2 2)) (dtr (+ mms_angle 270)) (/ rf1_size1 2)) (dtr (+ mms_angle 180)) 150)) ; brc2 cen line
    (setq br4 (polar (polar gu1 (dtr 90.0) (/ gusplate_wid2 2)) (dtr 180.0) 60)) ; brc2 cen line
  
    (setq br1_ang (rtd (angle br2 br1)))
    (setq brc1_length (+ (distance br1 br2) 70))
    ;; BRC-1
    ;  (cen)(command "_pline" (polar br1 (dtr br1_ang) 45) (polar br2 (dtr (+ br1_ang 180)) 25) "")
      (setq br5 (polar (polar br2 (dtr (+ br1_ang 270)) (/ brc1_size1 2)) (dtr (+ br1_ang 180)) 25 ))
      (setq br6 (polar br5 (dtr br1_ang) brc1_length))
      (setq br7 (polar br6 (dtr (+ br1_ang 90)) brc1_size1))
      (setq br8 (polar br7 (dtr (+ br1_ang 180)) brc1_length))
 ;     (mem) (command "_pline" br5 br6 br7 br8 "c")
 ;     (das) (command "_pline" (polar br5 (dtr (+ br1_ang 90)) brc1_tick) (polar br6 (dtr (+ br1_ang 90)) brc1_tick) "" ) ;tick line
 ;           (command "_pline" (polar br7 (dtr (+ br1_ang 270)) brc1_tick) (polar br8 (dtr (+ br1_ang 270)) brc1_tick) "" ) ;tick line
 ;     (des) (command "_pline" (polar br5 (dtr (+ br1_ang 90)) brc1_size3) (polar br6 (dtr (+ br1_ang 90)) brc1_size3) "" ) ;flange 2 line
 ;           (command "_pline" (polar br7 (dtr (+ br1_ang 270)) brc1_size3) (polar br8 (dtr (+ br1_ang 270)) brc1_size3) "" ) ;flange 2 line
 ;           (command "_text" "J" "L" (polar (polar br1 (dtr (+ 180 br1_ang)) (/ brc1_length 2)) (dtr (+ br1_ang 270)) 50) (+ br1_ang 180) "BRC-01") ;text
 ;           (12slottedholes (polar br1 (dtr br1_ang) 20) br1_ang)
 ;           (12slottedholes (polar br2 (dtr br1_ang) 30) br1_ang)
 ;           (12slottedholes br2 br1_ang)
 ;           (12slottedholes (polar br1 (dtr (+ br1_ang 180)) 20) br1_ang)
    ;; BRC-2
      (setq br2_ang (rtd (angle br4 br3)))
      (setq brc2_length (+ (distance br3 br4) 70))
 ;     (cen)(command "_pline" (polar br3 (dtr br2_ang) 45) (polar br4 (dtr (+ br2_ang 180)) 25) "")
      (setq br9 (polar (polar br4 (dtr (+ br2_ang 270)) (/ brc2_size1 2)) (dtr (+ br2_ang 180)) 25 ))
      (setq br10 (polar br9 (dtr br2_ang) brc2_length))
      (setq br11 (polar br10 (dtr (+ br2_ang 90)) brc2_size1))
      (setq br12 (polar br11 (dtr (+ br2_ang 180)) brc2_length))
  ;    (mem) (command "_pline" br9 br10 br11 br12 "c")

  ;    (das) (command "_pline" (polar br9 (dtr (+ br2_ang 90)) brc2_tick) (polar br10 (dtr (+ br2_ang 90)) brc2_tick) "" ) ;tick line
  ;          (command "_pline" (polar br11 (dtr (+ br2_ang 270)) brc2_tick) (polar br12 (dtr (+ br2_ang 270)) brc2_tick) "" ) ;tick line
  ;    (des) (command "_pline" (polar br9 (dtr (+ br2_ang 90)) brc2_size3) (polar br10 (dtr (+ br2_ang 90)) brc2_size3) "" ) ;flange 2 line
  ;          (command "_pline" (polar br11 (dtr (+ br2_ang 270)) brc2_size3) (polar br12 (dtr (+ br2_ang 270)) brc2_size3) "" ) ;flange 2 line
  ;          (command "_text" "J" "L" (polar (polar br4 (dtr br2_ang) 500) (dtr (+ br2_ang 90)) 50) br2_ang "BRC-02") ;text
  ;          (12slottedholes (polar br3 (dtr br2_ang) 20) br2_ang)
  ;          (12slottedholes (polar br4 (dtr br2_ang) 30) br2_ang)
  ;          (12slottedholes br4 br2_ang)
  ;          (12slottedholes (polar br3 (dtr (+ br2_ang 180)) 20) br2_ang)
    ;dimensions
  ;  (deflay)(command "dim1" "ali" raf1 raf2 (polar raf2 (dtr 90) 500) "")
  ;          (command "dim1" "ali" br7 br8 (polar br8 (dtr 270) 100) "")
  ;          (command "dim1" "ali" br9 br10 (polar br9 (dtr 270) 150) "")
  ;          (command "dim1" "ver" p1 ngl3 (polar p1 (dtr 180) 100) "")
  ;          (command "dim1" "ver" raf4 ngl3 (polar raf4 (dtr 180) 100) "")
  ;          (command "dim1" "ver" raf3 ngl4 (polar raf3 (dtr 0.0) 300) "")
  ;          (command "dim1" "ver" s12 ngl4 (polar s12 (dtr 0.0) 100) "")
;|          (command "UCS" "z" mms_angle)
  ;          (command "dim1" "ali" (inters br1 br2 raf13 raf14) s6 (polar s6 (dtr 90.0) 100) "")
  ;          (command "dim1" "ali" (inters br1 br2 raf13 raf14) s5 (polar s5 (dtr 90.0) 100) "")
  ;          (command "dim1" "ver" s5 (inters cen4 cen3 raf1 raf2) (polar s5 (dtr 90.0) 100) "")
  ;          (command "dim1" "ver" (inters cen4 cen3 raf1 raf2) s14 (polar s14 (dtr 90.0) 100) "")
  ;          (command "dim1" "ver" s14 (inters br3 br4 raf13 raf14) (polar s14 (dtr 90.0) 100) "")
  ;          (command "dim1" "ver" (inters br3 br4 raf13 raf14) s13 (polar s13 (dtr 90.0) 100) "") |;
  ;          (command "dim1" "hor" pl2 pl3 (polar pl2 (dtr 270.0) 100) "")
  ;          (command "dim1" "ver" pl3 pl4 (polar pl3 (dtr 0.0) 100) "")
  ;          (command "dim1" "ver" pl4 pl5 (polar pl4 (dtr 0.0) 100) "")
  ;          (command "dim1" "ver" pl5 gu1 (polar pl5 (dtr 0.0) 100) "")

            
    ;text
    ;hatch
    ;(mms_sections)
    (bom_text)
    (setq settings_mms_element 1)
)

(defun 12slottedholes(pp bolt_ang)
(setq temp1 (polar (polar pp (dtr (+ bolt_ang 90.0)) 5) (dtr (+ bolt_ang 0.0))5 ))
(setq temp2 (polar temp1 (dtr (+ bolt_ang 270.0)) 10))
(setq temp3 (polar temp2 (dtr (+ bolt_ang 180.0)) 8))
(setq temp4 (polar temp3 (dtr (+ bolt_ang 90.0)) 10))
(command "_pline" temp4 temp1 "arc" temp2 "line" temp3 "arc" temp4 ""))

(defun 9slottedholes(pp bolt_ang)
(setq temp1 (polar (polar pp (dtr (+ bolt_ang 90.0)) 4.5) (dtr (+ bolt_ang 0.0)) 2.5))
(setq temp2 (polar temp1 (dtr (+ bolt_ang 270.0)) 9))
(setq temp3 (polar temp2 (dtr (+ bolt_ang 180.0)) 5))
(setq temp4 (polar temp3 (dtr (+ bolt_ang 90.0)) 9))
(command "_pline" temp4 temp1 "arc" temp2 "line" temp3 "arc" temp4 ""))

(defun boltss (pp dia bolt_ang)
(setq cal1 (+ (/ dia 2) 6))
(setq temp1 (polar pp (dtr (+ bolt_ang 90.0)) cal1))
(setq temp2 (polar pp (dtr (+ bolt_ang 270.0)) cal1))
(setq temp3 (polar pp (dtr bolt_ang) cal1))
(setq temp4 (polar pp (dtr (+ bolt_ang 180.0)) cal1))
(bolt)(command "_circle" pp "dia" dia)
(cen)(command "_pline" temp1 temp2 "")(command "_pline" temp3 temp4 ""))

(defun purcleatbolts(pp)
    (setq temp1 (polar pp (dtr (+ mms_angle 180)) (/ pur_size2 2)))
    (setq temp1_1 (polar temp1 (dtr (+ mms_angle 180)) 7))
    (setq temp1_2 (polar temp1 (dtr mms_angle) 7))
    (command "_pline" (polar temp1 (dtr (+ mms_angle 90)) 3.5) (polar temp1 (dtr (+ mms_angle 270)) 3.5) "")
    (command "_pline" temp1_1 (polar temp1_1 (dtr (+ mms_angle 90)) 2) "")
    (command "_pline" temp1_2 (polar temp1_2 (dtr (+ mms_angle 90)) 2) "")
  
    (setq temp3 (polar pp (dtr mms_angle) (/ pur_size2 2)))
    (setq temp3_1 (polar temp3 (dtr (+ mms_angle 180)) 7))
    (setq temp3_2 (polar temp3 (dtr mms_angle) 7))
    (command "_pline" (polar temp3 (dtr (+ mms_angle 90)) 3.5) (polar temp3 (dtr (+ mms_angle 270)) 3.5) "")
    (command "_pline" temp3_1 (polar temp3_1 (dtr (+ mms_angle 90)) pur_tick) "")
    (command "_pline" temp3_2 (polar temp3_2 (dtr (+ mms_angle 90)) pur_tick) "")
  
    (setq temp4 (polar (polar pp (dtr (+ mms_angle 90)) pur_size1) (dtr mms_angle) (/ pur_size2 2)))
    (setq temp4_1 (polar temp4 (dtr (+ mms_angle 180)) 7))
    (setq temp4_2 (polar temp4 (dtr mms_angle) 7)) 
    
    (command "_pline" (polar temp4 (dtr (+ mms_angle 90)) 3.5) (polar temp4 (dtr (+ mms_angle 270)) 3.5) "")
    (command "_pline" temp4_1 (polar temp4_1 (dtr (+ mms_angle 270)) pur_tick) "")
    (command "_pline" temp4_2 (polar temp4_2 (dtr (+ mms_angle 270)) pur_tick) "")

    (setq temp2 (polar pp (dtr (+ 90 mms_angle)) (/ (- Pur_size1 5) 2))) ; bolt2
        (setq temp2_1 (polar temp2 (dtr (+ mms_angle 90)) 7))
        (setq temp2_2 (polar temp2 (dtr (+ mms_angle 270)) 7))
        (command "_pline" (polar temp2 (dtr (+ mms_angle 180)) 3.5) (polar temp2 (dtr mms_angle) 3.5) "")
        (command "_pline" temp2_1 (polar temp2_1 (dtr (+ mms_angle 180)) 2) "")
        (command "_pline" temp2_2 (polar temp2_2 (dtr (+ mms_angle 180)) 2) "")
        (command "_pline" temp2_1 (polar temp2_1 (dtr mms_angle) pur_tick) "")
        (command "_pline" temp2_2 (polar temp2_2 (dtr mms_angle) pur_tick) "")


;| (if (< pur_size1 80) 
      (progn
        (setq temp2 (polar pp (dtr (+ 90 mms_angle)) (/ (- Pur_size1 5) 2))) ; bolt2
        (setq temp2_1 (polar temp2 (dtr (+ mms_angle 90)) 7))
        (setq temp2_2 (polar temp2 (dtr (+ mms_angle 270)) 7))
        (command "_pline" (polar temp2 (dtr (+ mms_angle 180)) 3.5) (polar temp2 (dtr mms_angle) 3.5) "")
        (command "_pline" temp2_1 (polar temp2_1 (dtr (+ mms_angle 180)) 2) "")
        (command "_pline" temp2_2 (polar temp2_2 (dtr (+ mms_angle 180)) 2) "")
        (command "_pline" temp2_1 (polar temp2_1 (dtr mms_angle) pur_tick) "")
        (command "_pline" temp2_2 (polar temp2_2 (dtr mms_angle) pur_tick) "")
        )
        )
  (if (< pur_size1 80)
  (progn
    (setq temp2 (polar pp (dtr (+ 90 mms_angle)) 20)) ; bolt2
    (setq temp2_1 (polar temp2 (dtr (+ mms_angle 90)) 7))
    (setq temp2_2 (polar temp2 (dtr (+ mms_angle 270)) 7))
    (setq temp22 (polar temp2 (dtr (+ 90 mms_angle)) (- Pur_size1 45) 2)) ; bolt2
    (setq temp22_1 (polar temp2 (dtr (+ mms_angle 90)) 7))
    (setq temp22_2 (polar temp2 (dtr (+ mms_angle 270)) 7))
    (command "_pline" (polar temp2 (dtr (+ mms_angle 180)) 3.5) (polar temp2 (dtr mms_angle) 3.5) "")
    (command "_pline" temp2_1 (polar temp2_1 (dtr (+ mms_angle 180)) 2) "")
    (command "_pline" temp2_2 (polar temp2_2 (dtr (+ mms_angle 180)) 2) "")
    (command "_pline" temp2_1 (polar temp2_1 (dtr mms_angle) pur_tick) "")
    (command "_pline" temp2_2 (polar temp2_2 (dtr mms_angle) pur_tick) "")

    (command "_pline" (polar temp22 (dtr (+ mms_angle 180)) 3.5) (polar temp2 (dtr mms_angle) 3.5) "")
    (command "_pline" temp22_1 (polar temp22_1 (dtr (+ mms_angle 180)) 2) "")
    (command "_pline" temp22_2 (polar temp22_2 (dtr (+ mms_angle 180)) 2) "")
    (command "_pline" temp22_1 (polar temp22_1 (dtr mms_angle) pur_tick) "")
    (command "_pline" temp22_2 (polar temp22_2 (dtr mms_angle) pur_tick) "")
    )
   ) |;
)

(defun bom_text()
  ; DESCRIPTION
  (setq bom1 (polar p1 (dtr 180.0) 5000))
  (setq bom1_1 (polar bom1 (dtr 90) 100))
  (setq bom2 (polar bom1 (dtr 270) 100))
  (setq bom3 (polar bom2 (dtr 270) 100))
  (setq bom4 (polar bom3 (dtr 270) 100))
  (setq bom5 (polar bom4 (dtr 270) 100))
  (setq bom6 (polar bom5 (dtr 270) 100))
  (setq bom7 (polar bom6 (dtr 270) 100))
  (setq bom8 (polar bom7 (dtr 270) 100))
  (setq bom9 (polar bom8 (dtr 270) 100))
  (setq bom10 (polar bom9 (dtr 270) 100))
  (setq bom11 (polar bom10 (dtr 270) 100))
  (setq bom12 (polar bom11 (dtr 270) 100))
  (setq bom13 (polar bom12 (dtr 270) 100))
  (setq bom14 (polar bom13 (dtr 270) 100))
  (setq bom15 (polar bom14 (dtr 270) 100))

  (command "_text" "J" "L" bom1_1 "0" "DESCRIPTION")
  (command "_text" "J" "L" bom1 "0" "LEG-1")
  (command "_text" "J" "L" bom2 "0" "LEG-2")
  (command "_text" "J" "L" bom3 "0" "Purlin")
  (command "_text" "J" "L" bom4 "0" "Rafter")
  (command "_text" "J" "L" bom5 "0" "BRC-01")
  (command "_text" "J" "L" bom6 "0" "BRC-02")
  (command "_text" "J" "L" bom7 "0" "BRC-03")
  (command "_text" "J" "L" bom8 "0" "SA-01")
  (command "_text" "J" "L" bom9 "0" "CLT-1")
  (command "_text" "J" "L" bom10 "0" "CLT-2")
  (command "_text" "J" "L" bom11 "0" "GUS Plate")

  ;size
(setq bom16 (polar bom1 (dtr 0.0) 350))
(setq bom16_1 (polar bom1_1 (dtr 0.0) 350))
(setq bom17 (polar bom2 (dtr 0.0) 350))
(setq bom18 (polar bom3 (dtr 0.0) 350))
(setq bom19 (polar bom4 (dtr 0.0) 350))
(setq bom20 (polar bom5 (dtr 0.0) 350))
(setq bom21 (polar bom6 (dtr 0.0) 350))
(setq bom22 (polar bom7 (dtr 0.0) 350))
(setq bom23 (polar bom8 (dtr 0.0) 350))
(setq bom24 (polar bom9 (dtr 0.0) 350))
(setq bom25 (polar bom10 (dtr 0.0) 350))
(setq bom26 (polar bom11 (dtr 0.0) 350))
(setq bom27 (polar bom12 (dtr 0.0) 350))
(setq bom28 (polar bom13 (dtr 0.0) 350))
(setq bom29 (polar bom14 (dtr 0.0) 350))
(setq bom30 (polar bom15 (dtr 0.0) 350))
(command "_text" "J" "L" bom16_1 "0" "Size")
(command "_text" "J" "L" bom16 "0" (strcat (rtos leg1_size1) "x" (rtos leg1_size2) "x" (rtos leg1_size3) "x" (rtos leg1_tick)))
(command "_text" "J" "L" bom17 "0" (strcat (rtos leg3_size1) "x" (rtos leg3_size2) "x" (rtos leg1_tick)))
(command "_text" "J" "L" bom18 "0" (strcat (rtos Pur_size1) "x" (rtos pur_size2) "x" (rtos pur_size3) "x" (rtos pur_tick)))
(command "_text" "J" "L" bom19 "0" (strcat (rtos rf1_size1) "x" (rtos rf1_size2) "x" (rtos rf1_size3) "x" (rtos rf1_tick)))
(command "_text" "J" "L" bom20 "0" (strcat (rtos brc1_size1) "x" (rtos brc1_size2) "x" (rtos brc1_size3) "x" (rtos brc1_tick)))
(command "_text" "J" "L" bom21 "0" (strcat (rtos brc2_size1) "x" (rtos brc2_size2) "x" (rtos brc2_size3) "x" (rtos brc2_tick)))
(command "_text" "J" "L" bom22 "0" (strcat (rtos brc3_size1) "x" (rtos brc3_size2) "x" (rtos brc3_size3) "x" (rtos brc3_tick)))
(command "_text" "J" "L" bom23 "0" "L40x40x1")
(command "_text" "J" "L" bom24 "0" (strcat (rtos (- Pur_size1 5)) "x40x1"))
(command "_text" "J" "L" bom25 "0" (strcat (rtos (- Pur_size1 5)) "x" (rtos pur_size2) "x2"))
(command "_text" "J" "L" bom26 "0" "320x100x3")

  ;QTY
(setq bom31 (polar bom16 (dtr 0.0) 500))
(setq bom31_1 (polar bom16_1 (dtr 0.0) 500))
(setq bom32 (polar bom17 (dtr 0.0) 500))
(setq bom33 (polar bom18 (dtr 0.0) 500))
(setq bom34 (polar bom19 (dtr 0.0) 500))
(setq bom35 (polar bom20 (dtr 0.0) 500))
(setq bom36 (polar bom21 (dtr 0.0) 500))
(setq bom37 (polar bom22 (dtr 0.0) 500))
(setq bom38 (polar bom23 (dtr 0.0) 500))
(setq bom39 (polar bom24 (dtr 0.0) 500))
(setq bom40 (polar bom25 (dtr 0.0) 500))
(setq bom41 (polar bom26 (dtr 0.0) 500))
(setq bom42 (polar bom27 (dtr 0.0) 500))
(setq bom43 (polar bom28 (dtr 0.0) 500))
(setq bom44 (polar bom29 (dtr 0.0) 500))
(setq bom45 (polar bom30 (dtr 0.0) 500))

(setq num_leg1 (+ number_of_piles 1))
(setq num_leg3 (+ number_of_piles 1))
(setq num_pur 4)
(setq num_raf (+ number_of_piles 1))
(setq num_brc1 (+ number_of_piles 1))
(setq num_brc2 (+ number_of_piles 1))
(setq num_brc3 2)
(setq num_sa1 number_of_piles)
(setq num_clt1 (rtos (/ number_of_piles 2) 2 0))
(setq num_clt2 (* (+ number_of_piles 1) 4) )
(setq num_gus (+ number_of_piles 1))
(command "_text" "J" "L" bom31_1 "0" "QTY")
(command "_text" "J" "L" bom31 "0" num_leg1)
(command "_text" "J" "L" bom32 "0" num_leg3)
(command "_text" "J" "L" bom33 "0" num_pur)
(command "_text" "J" "L" bom34 "0" num_raf)
(command "_text" "J" "L" bom35 "0" num_brc1)
(command "_text" "J" "L" bom36 "0" num_brc2)
(command "_text" "J" "L" bom37 "0" num_brc3)
(command "_text" "J" "L" bom38 "0" num_sa1)
(command "_text" "J" "L" bom39 "0" num_clt1)
(command "_text" "J" "L" bom40 "0" num_clt2)
(command "_text" "J" "L" bom41 "0" num_gus)

  ;length
(setq bom46 (polar bom31 (dtr 0.0) 250))
(setq bom46_1 (polar bom31_1 (dtr 0.0) 250))
(setq bom47 (polar bom32 (dtr 0.0) 250))
(setq bom48 (polar bom33 (dtr 0.0) 250))
(setq bom49 (polar bom34 (dtr 0.0) 250))
(setq bom50 (polar bom35 (dtr 0.0) 250))
(setq bom51 (polar bom36 (dtr 0.0) 250))
(setq bom52 (polar bom37 (dtr 0.0) 250))
(setq bom53 (polar bom38 (dtr 0.0) 250))
(setq bom54 (polar bom39 (dtr 0.0) 250))
(setq bom55 (polar bom40 (dtr 0.0) 250))
(setq bom56 (polar bom41 (dtr 0.0) 250))
(setq bom57 (polar bom42 (dtr 0.0) 250))
(setq bom58 (polar bom43 (dtr 0.0) 250))
(setq bom59 (polar bom44 (dtr 0.0) 250))
(setq bom60 (polar bom45 (dtr 0.0) 250))

(setq len_leg1 (rtos (distance lg10 lg11) 2 0))
(setq len_leg3 leg3_length)
(setq len_pur mms_table_length)
(setq len_raf (rtos Rafter_length 2 0))
(setq len_brc1 (rtos brc1_length 2 0))
(setq len_brc2 (rtos brc2_length 2 0))
(setq len_brc3 (rtos (* 1.15 table_pile_cc) 2 0 ))
(setq len_sa1 (rtos Rafter_length 2 0))
(setq len_clt1 rf1_size2)
(setq len_clt2 40)
(setq len_gus "-")
(command "_text" "J" "L" bom46_1 "0" "Length")
(command "_text" "J" "L" bom46 "0" len_leg1)
(command "_text" "J" "L" bom47 "0" len_leg3)
(command "_text" "J" "L" bom48 "0" len_pur)
(command "_text" "J" "L" bom49 "0" len_raf)
(command "_text" "J" "L" bom50 "0" len_brc1)
(command "_text" "J" "L" bom51 "0" len_brc2)
(command "_text" "J" "L" bom52 "0" len_brc3)
(command "_text" "J" "L" bom53 "0" len_sa1)
(command "_text" "J" "L" bom54 "0" len_clt1)
(command "_text" "J" "L" bom55 "0" len_clt2)
(command "_text" "J" "L" bom56 "0" len_gus)

  ;unit weight
(setq bom61 (polar bom46 (dtr 0.0) 350))
(setq bom61_1 (polar bom46_1 (dtr 0.0) 250))
(setq bom62 (polar bom47 (dtr 0.0) 350))
(setq bom63 (polar bom48 (dtr 0.0) 350))
(setq bom64 (polar bom49 (dtr 0.0) 350))
(setq bom65 (polar bom50 (dtr 0.0) 350))
(setq bom66 (polar bom51 (dtr 0.0) 350))
(setq bom67 (polar bom52 (dtr 0.0) 350))
(setq bom68 (polar bom53 (dtr 0.0) 350))
(setq bom69 (polar bom54 (dtr 0.0) 350))
(setq bom70 (polar bom55 (dtr 0.0) 350))
(setq bom71 (polar bom56 (dtr 0.0) 350))
(setq bom72 (polar bom57 (dtr 0.0) 350))
(setq bom73 (polar bom58 (dtr 0.0) 300))
(setq bom74 (polar bom59 (dtr 0.0) 250))
(setq bom75 (polar bom60 (dtr 0.0) 250))

(setq sa1_unitweight 0.95)
(setq gus_unitweight 0.75)

(setq clt1_ri (* 1.5 1))
(setq clt1_ro (+ clt1_ri 1))
(setq clt1_area (+ (- (- Pur_size1 5) clt1_ro clt1_ro) (- 40 clt1_ro) (- 40 clt1_ro) (* (/ 3.141592654 4) 2 (- (* clt1_ro clt1_ro) (* clt1_ri clt1_ri)))))
(setq clt1_unitweight (rtos (* clt1_area 7850 0.01 0.01 0.01) 2 2))

(setq clt2_ri (* 1.5 2))
(setq clt2_ro (+ clt1_ri 2))
(setq clt2_area (+ (- (- Pur_size1 5) clt2_ro) (- Pur_size2 clt2_ro) (* (/ 3.141592654 4) (- (* clt2_ro clt2_ro) (* clt2_ri clt2_ri)))))
(setq clt2_unitweight (rtos (* clt1_area 7850 0.01 0.01 0.01) 2 2))

(command "_text" "J" "L" bom61_1 "0" "Unit Weight")
(command "_text" "J" "L" bom61 "0" (rtos leg1_unitweight 2 2))
(command "_text" "J" "L" bom62 "0" (rtos leg3_unitweight 2 2))
(command "_text" "J" "L" bom63 "0" (rtos purlin_unitweight 2 2))
(command "_text" "J" "L" bom64 "0" (rtos rafter_unitweight 2 2))
(command "_text" "J" "L" bom65 "0" (rtos brc01_unitweight 2 2))
(command "_text" "J" "L" bom66 "0" (rtos brc02_unitweight 2 2))
(command "_text" "J" "L" bom67 "0" (rtos brc03_unitweight 2 2))
(command "_text" "J" "L" bom68 "0" sa1_unitweight)
(command "_text" "J" "L" bom69 "0" clt1_unitweight)
(command "_text" "J" "L" bom70 "0" clt2_unitweight)
(command "_text" "J" "L" bom71 "0" gus_unitweight)
;Weight
(setq bom76 (polar bom61 (dtr 0.0) 350))
(setq bom76_1 (polar bom61_1 (dtr 0.0) 350))
(setq bom77 (polar bom62 (dtr 0.0) 350))
(setq bom78 (polar bom63 (dtr 0.0) 350))
(setq bom79 (polar bom64 (dtr 0.0) 350))
(setq bom80 (polar bom65 (dtr 0.0) 350))
(setq bom81 (polar bom66 (dtr 0.0) 350))
(setq bom82 (polar bom67 (dtr 0.0) 350))
(setq bom83 (polar bom68 (dtr 0.0) 350))
(setq bom84 (polar bom69 (dtr 0.0) 350))
(setq bom85 (polar bom70 (dtr 0.0) 350))
(setq bom86 (polar bom71 (dtr 0.0) 350))
(setq bom87 (polar bom72 (dtr 0.0) 350))
(setq bom88 (polar bom73 (dtr 0.0) 300))
(setq bom89 (polar bom74 (dtr 0.0) 350))
(setq bom90 (polar bom75 (dtr 0.0) 350))

(setq weight_leg1 (* (atof len_leg1) leg1_unitweight num_leg1 0.001))
(setq weight_leg3 (* leg3_length leg3_unitweight num_leg3 0.001))
(setq weight_pur (* len_pur purlin_unitweight num_pur 0.001 ))
(setq weight_raf (* (atof len_raf) rafter_unitweight num_raf 0.001))
(setq weight_brc1 (* ( atof len_brc1) brc01_unitweight num_brc1 0.001))
(setq weight_brc2 (* (atof len_brc2) brc02_unitweight num_brc2 0.001))
(setq weight_brc3 (* len_brc3 brc03_unitweight num_brc3 0.001))
(setq weight_sa1 (* (atof len_sa1) sa1_unitweight num_sa1 0.001))
(setq weight_clt1 (* len_clt1 (atof clt1_unitweight) (atof num_clt1) 0.001))
(setq weight_clt2 (* len_clt2 (atof clt2_unitweight) num_clt2 0.001))
(setq weight_gus (* gus_unitweight num_gus))
(setq Total_Weight (+ weight_leg1 weight_leg3 weight_pur weight_raf weight_brc1 weight_brc2 weight_brc3 weight_sa1 weight_clt1 weight_clt2 weight_gus))

(command "_text" "J" "L" bom76_1 "0" "Weight")
(command "_text" "J" "L" bom76 "0" (rtos weight_leg1 2 1))
(command "_text" "J" "L" bom77 "0" (rtos weight_leg3 2 1))
(command "_text" "J" "L" bom78 "0" (rtos weight_pur 2 1))
(command "_text" "J" "L" bom79 "0" (rtos weight_raf 2 1))
(command "_text" "J" "L" bom80 "0" (rtos weight_brc1 2 1))
(command "_text" "J" "L" bom81 "0" (rtos weight_brc2 2 1))
(command "_text" "J" "L" bom82 "0" (rtos weight_brc3 2 1))
(command "_text" "J" "L" bom83 "0" (rtos weight_sa1 2 1))
(command "_text" "J" "L" bom84 "0" (rtos weight_clt1 2 1))
(command "_text" "J" "L" bom85 "0" (rtos weight_clt2 2 1))
(command "_text" "J" "L" bom86 "0" (rtos weight_gus 2 1))
(des)(command "_text" "J" "L" bom87 "0" (rtos Total_Weight 2 1))


)

(defun mms_sections()
  (setq mms_sec_p1 (polar p1 (dtr 225.0) 10000))
  (setq mms_sec_p2 mms_sec_p1) ;shifting point
  (setq i 0)
  (repeat (+ number_of_piles 1)
    (setq mms_sec_p3 (polar mms_sec_p2 (dtr 90.0) 2000))
    (setq mms_sec_p4 (polar mms_sec_p2 (dtr 270.0) 3000))
    (cen)(command "_pline" mms_sec_p3 mms_sec_p4 "")
    (setq mms_sec_p5 (polar (polar mms_sec_p2 (dtr 0.0) (/ leg1_size2 2)) (dtr 90.0) (- (/ leg1_size1 2) leg1_size3 )))
    ;c-section with Lip
    (setq mms_sec_p6 (polar mms_sec_p5 (dtr 90.0) leg1_size3))
    (setq mms_sec_p7 (polar mms_sec_p6 (dtr 180.0) leg1_size2))
    (setq mms_sec_p8 (polar mms_sec_p7 (dtr 270.0) leg1_size1))
    (setq mms_sec_p9 (polar mms_sec_p8 (dtr 0.0) leg1_size2))
    (setq mms_sec_p10 (polar mms_sec_p9 (dtr 90.0) leg1_size3))
    (setq mms_sec_p11 (polar mms_sec_p10 (dtr 180.0) leg1_tick))
    (setq mms_sec_p12 (polar mms_sec_p11 (dtr 270.0) (- leg1_size3 leg1_tick)))
    (setq mms_sec_p13 (polar mms_sec_p12 (dtr 180.0) (- leg1_size2 leg1_tick leg1_tick)))
    (setq mms_sec_p14 (polar mms_sec_p13 (dtr 90.0) (- leg1_size1 leg1_tick leg1_tick)))
    (setq mms_sec_p15 (polar mms_sec_p14 (dtr 0.0) (- leg1_size2 leg1_tick leg1_tick)))
    (setq mms_sec_p16 (polar mms_sec_p15 (dtr 270.0) (- leg1_size3 leg1_tick)))
    (color8)(command "_pline" mms_sec_p5 mms_sec_p6 mms_sec_p7 mms_sec_p8 mms_sec_p9 mms_sec_p10 mms_sec_p11 mms_sec_p12 mms_sec_p13 mms_sec_p14 mms_sec_p15 mms_sec_p16 "c")
    (color8)(command "_circle" mms_sec_p2 pile_dia)
            (command "hatch" "AR-CONC" "0.5" "0" "l" "")
    (setq i (1+ i))
   (if (< i number_of_piles) (setq mms_sec_p2 (polar mms_sec_p2 (dtr 0.0) table_pile_cc)))
  )
  (setq rf_cal1 (distance raf13 (inters cen4 cen3 raf13 raf14) ))
  (setq rf_cal2 (distance raf14 (inters cen4 cen3 raf13 raf14) ))
  (setq mms_sec_p17 (polar (polar mms_sec_p1 (dtr 180) mms_table_overhang) (dtr 90) rf_cal2))
  (setq mms_sec_p18 (polar mms_sec_p17 (dtr 0) mms_table_length))
  (setq mms_sec_p19 (polar mms_sec_p18 (dtr 270) mms_table_width))
  (setq mms_sec_p20 (polar mms_sec_p19 (dtr 180) mms_table_length))
  (bolt) (command "_pline" mms_sec_p17 mms_sec_p18 mms_sec_p19 mms_sec_p20 "c")
  (setq mms_sec_p21 mms_sec_p17)
   (repeat table_size
    (solar_module mms_sec_p21)
    (setq mms_sec_p22 (polar mms_sec_p21 (dtr 270) (+ table_module_gap module_length)))
    (solar_module mms_sec_p22)
    (setq mms_sec_p21 (polar mms_sec_p21 (dtr 0.0) (+ table_module_gap module_wid)))
    )

)

(defun solar_module(xx)
  (setq solar1 xx)
  (setq solar2 (polar solar1 (dtr 0.0) module_wid))
  (setq solar3 (polar solar2 (dtr 270.0) module_length))
  (setq solar4 (polar solar3 (dtr 180.0) module_wid))
 ; (setq solar5 (polar solar4 (dtr 0.0) module_length))
  (command "_pline" solar1 solar2 solar3 solar4 "c")

  (setq solar6 (polar (polar solar1 (dtr 0.0) (/ (- module_wid module_wid_boltgap) 2)) (dtr 270) module_bolt1))
  (setq solar7 (polar solar6 (dtr 270) module_boltgap))
  (setq solar8 (polar (polar solar2 (dtr 180.0) (/ (- module_wid module_wid_boltgap) 2)) (dtr 270) module_bolt1))
  (setq solar9 (polar solar8 (dtr 270) module_boltgap))
  (9slottedholes solar6 90)(9slottedholes solar7 90)(9slottedholes solar8 90)(9slottedholes solar9 90)

  (setq solar10 (polar (polar solar1 (dtr 0.0) (- module_wid module_wid_boltgap)) (dtr 270) (- module_wid module_wid_boltgap)))
  (setq solar11 (polar (polar solar2 (dtr 180.0) (- module_wid module_wid_boltgap)) (dtr 270) (- module_wid module_wid_boltgap)))
  (setq solar12 (polar (polar solar3 (dtr 180.0) (- module_wid module_wid_boltgap)) (dtr 90) (- module_wid module_wid_boltgap)))
  (setq solar13 (polar (polar solar4 (dtr 0.0) (- module_wid module_wid_boltgap)) (dtr 90) (- module_wid module_wid_boltgap)))
  (command "_pline" solar1 solar10 "")(command "_pline" solar2 solar11 "")(command "_pline" solar3 solar12 "")(command "_pline" solar4 solar13 "")
  (command "_pline" solar10 solar11 solar12 solar13 "c")
  (color8)(command "hatch" "ANSI37" "100" "45" "l" "")

)

(defun settings_mms()
(if (= settings_mms_element nil)
    (progn

      (command "layer" "m" "mem" "c" "4" "" "lw" "0.2" "" "")
      (command "layer" "m" "8" "c" "8" "" "lw" "0.2" "" "")
      (command "layer" "m" "des" "c" "1" "" "lw" "0.09" "" "")
      (command "layer" "m" "gus" "c" "3" "" "lw" "0.2" "" "")
      (command "layer" "m" "con" "c" "1" "" "lw" "0.09" "" "")
      (command "layer" "m" "dim" "c" "2" "" "lw" "0.2" "" "")
      (command "dimlwd" 9) (command "dimlwe" 9)
      (command "layer" "m" "text" "c" "2" "" "lw" "0.2" "" "")
      (command "layer" "m" "bolt" "c" "4" "" "lw" "0.2" "" "")
      (command "layer" "m" "bdes" "c" "31" "" "lw" "0.2" "" "")
      (command "layer" "m" "das" "c" "1" "" "lt" "HIDDEN" "" "lw" "0.09" "" "")
      (command "layer" "m" "cen" "c" "2" "" "lt" "center" "" "lw" "0.09" "" "")
      (command "layer" "m" "cen1" "c" "31" "" "lt" "center" "" "lw" "0.09" "" "")
      (command "layer" "s" "0" "")

      (defun mem() (command "layer" "s" "mem" ""))
      (defun cen() (command "layer" "s" "cen" ""))
      (defun das() (command "layer" "s" "das" ""))
      (defun dim() (command "layer" "s" "dim" ""))
      (defun des() (command "layer" "s" "des" ""))
      (defun bolt() (command "layer" "s" "bolt" ""))
      (defun color8() (command "layer" "s" "8" ""))
      (defun deflay() (command "layer" "s" "0" ""))

      (command "dimscale" 15)
      (command "style" "arial" "arial" (* 4.0 15) "" "" "" "")
      (command "style" "standard" "simplex" (* 2.5 15) "0.8" "" "" "" "")
      (command "style" "SHX_style" "simplex" (* 2.5 15) "0.8" "" "" "" "")
      (command "ltscale" (* 5.0 15))
      (command "dimasz" 2.5)
      (command "dimtsz" 0.5)
      (command "dimtxt" 2.5)
      (command "dimexe" 1.25)
      (command "dimexo" 1)
      (command "dimlwd" 9)
      (command "dimlwe" 9)
      (command "dimgap" 1)
      (command "dimtad" 1)
      (command "dimtofl" 1)
      (command "dimtih" 0)
      (command "dimtoh" 0)
      (command "dimfxlon" 0)
      (command "dimse1" 0)
      (command "dimse2" 0)
      (command "dimdec" 0)
      (command "LTS" 1)
    )  
  )
)


(defun mms_nil()
  (setq module_wid nil)
  (setq module_wid_boltgap nil)
  (setq module_bolt1 nil)
  (setq module_boltgap nil)
  (setq module_botl2 nil)
  (setq module_length nil)
  (setq mms_angle nil)
  (setq mms_base_hight nil)
  (setq mms_gus_gap nil)
  (setq leg1_size1 nil)
  (setq leg1_size2 nil)
  (setq leg1_size3 nil)
  (setq leg1_tick nil)
  (setq leg3_size1 nil)
  (setq leg3_size2 nil)
  (setq leg3_size3 nil)
  (setq leg3_tick nil)
  (setq brc1_size1 nil)
  (setq brc1_size2 nil)
  (setq brc1_size3 nil)
  (setq brc1_tick nil)
  (setq brc2_size1 nil)
  (setq brc2_size2 nil)
  (setq brc2_size3 nil)
  (setq brc2_tick nil)
  (setq brc3_size1 nil)
  (setq brc3_size2 nil)
  (setq brc3_size3 nil)
  (setq brc3_tick nil)
  (setq rf1_size1 nil)
  (setq rf1_size2 nil)
  (setq rf1_size3 nil)
  (setq rf1_tick nil)
  (setq pur_size1 nil)
  (setq pur_size2 nil)
  (setq pur_size3 nil)
  (setq pur_tick nil)
  (setq pile_dia nil)
  (setq pile_len nil)
  (setq pile_cap nil)
  (setq string_size nil)
  (setq p1 nil)
  (setq mms_table_overhang nil)
  (setq number_of_piles nil)
  (setq mms_table_width nil)
  (setq mms_table_length nil)
)
